module AaaCertManagerConsumer {
    yang-version 1;
    namespace "urn:opendaylight:params:xml:ns:yang:AaaCertManagerConsumer";
    prefix "AaaCertManagerConsumer";

    revision "2015-01-05" {
        description "Initial revision of AaaCertManagerConsumer model";
    }
}
